Attribute VB_Name = "Module1"
'       Экспорт данных текущего слоя в Microsoft Word
'       Copyright (C) 1999 by Александр Беляев
'
'       Главный модуль проекта



Option Explicit

Public Type RefRecType
    SKey As Double
    SKey1 As Double
    SKeyX As Double
    SKeyY As Double
    SKey1X As Double
    SKey1Y As Double
    SSIndex As Integer
End Type

Public Const appName = "Экспорт данных в MS Word"
Public Const C_PolylineObjectName = "AcDbPolyline"

' Version of Excel that's available to us. This will be
' set to 7, 8, or 0 -- older versions do us no good.
' Set by the ConnectExcel procedure
Public WordVer As Integer
Public WordServer As Object
    
Public Sub ExportToTheWord()
Attribute ExportToTheWord.VB_Description = "Вывод таблицы координат полигонов текущего слоя в MS Word"
    'UserForm1.ACADInfoBox.Text = GetACADInfo()
    If Not (ACADHasOpenedDrawing) Then End
    
    IterateLayers
    
    UserForm1.Show
    UserForm1.hide
End Sub

Function GetACADInfo() As String
    Dim ACADApp As AcadApplication
    On Error Resume Next
        
    Set ACADApp = GetObject(, "AutoCAD.Application")
    If Err Then
        MsgBox "Немогу связаться с программой AutoCAD (" + Err.Description, , appName
        End
       End If
    GetACADInfo = ACADApp.Name + " version " + ACADApp.Version
End Function

Function ACADHasOpenedDrawing() As Boolean
    ACADHasOpenedDrawing = False
    
    If Documents.count = 0 Then
        MsgBox "Сначала откройте необходимый вам чертеж", , appName
    Else
        ACADHasOpenedDrawing = True
    End If
End Function

Private Sub IterateLayers()
    On Error Resume Next
    
    UserForm1.LayerSelectComboBox.Clear
    
    Dim i, n As Integer
    n = 0
    For i = 0 To ThisDrawing.Layers.count - 1
        UserForm1.LayerSelectComboBox.AddItem (ThisDrawing.Layers.Item(i).Name)
        If ThisDrawing.ActiveLayer.Name = ThisDrawing.Layers.Item(i).Name Then
            n = i
        End If
    Next
    UserForm1.LayerSelectComboBox.ListIndex = n

End Sub

Function ExportData(ByVal bAreaOnly As Boolean)
    
    Dim DrawingObject As AcadObject
    Dim ExtensionDictionaryResults As String
    Dim entity As AcadEntity
    Dim PolyLine As AcadLWPolyline
    Dim i, j, k, YP, XP, nPage, nColNum, nCounter, nLastYP, tt As Integer
    Dim SumArea As Double
    Dim objWorkDoc As Object
    ReDim ssobjs(0) As AcadEntity
    ReDim RefArr(0) As RefRecType
    
    
    Dim retCoord As Variant
    Dim pointUCS As Variant
    Dim OnePoint(0 To 2) As Double
    Dim XRep, YRep As String
    Dim aTable, aCell As Variant
    
    Dim Hyperlinks As AcadHyperlinks
    Dim Hyperlink As AcadHyperlink
    
    'GetProjectFilePath
    'MsgBox ThisDrawing.Application.VBE.Protection
    '.FullName
    'VBE.ActiveVBProject.Name
    '.Description
    'ThisDrawing.RegisteredApplications.count
    
    'Dim appName As String
    'appName = ThisDrawing.RegisteredApplications
    'Application.FullName
    'MsgBox "The full name of the current application is " & appName, , "FullName Example"
    


    
    If ThisDrawing.ModelSpace.count = 0 Then
        MsgBox "Чертеж пуст - нечего экспортировать."
        Exit Function
    End If
  
    For Each entity In ThisDrawing.ModelSpace
        If (entity.Layer = UserForm1.LayerSelectComboBox.Text) And _
           (entity.ObjectName = C_PolylineObjectName) And _
           (entity.Visible) Then
            Set PolyLine = entity
            If (PolyLine.Closed) Then
                ExtensionDictionaryResults = ExtensionDictionaryResults & _
                PolyLine.Area & "\" & entity.ObjectName & " - " & entity.PlotStyleName & ";  "
                
                Set ssobjs(UBound(ssobjs)) = entity
                With RefArr(UBound(RefArr))
                    GetVal entity, RefArr(UBound(RefArr))
                    .SSIndex = UBound(RefArr)
                End With
                
                ReDim Preserve ssobjs(UBound(ssobjs) + 1)
                ReDim Preserve RefArr(UBound(RefArr) + 1)
                
                SumArea = SumArea + PolyLine.Area
            End If
        End If
        DoEvents
    Next
    
    If UBound(ssobjs) = 0 Then
        MsgBox "Слой '" & UserForm1.LayerSelectComboBox.Text & _
            "' не содержит подходящих полигонов"
        Exit Function
    End If
    
    If bAreaOnly Then
       ShowAreaForm.TB_LayerName.Text = UserForm1.LayerSelectComboBox.Text
       ShowAreaForm.TB_PolyNumber.Text = UBound(ssobjs)
       ShowAreaForm.TB_SumArea.Text = Format(SumArea, "0.0000")
       ShowAreaForm.Show
       Exit Function
    End If
    
    ConnectWord (0)
    
    If WordVer = 0 Then
       Exit Function
    Else:
    End If
    
    ' Удаляем автоматически добавленный последний элемент массива
    ReDim Preserve ssobjs(UBound(ssobjs) - 1)
    ReDim Preserve RefArr(UBound(RefArr) - 1)
                    
    ' Сортируем полигоны если кол-во больше 1-го
    If UBound(RefArr) <> 0 Then QuickSortPolylines RefArr, LBound(RefArr), UBound(RefArr)
                        
    If Dir("c:\fineTable.dot") = "" Then
        MsgBox "Нет необходимого файла 'c:\fineTable.dot'"
        Exit Function
    End If
            
    Set objWorkDoc = WordServer.Documents.Add("c:\fineTable.dot")
    
    On Error GoTo ОбработкаОшибок
    
    WordServer.Visible = False
    WordServer.ScreenUpdating = False
    
    UserForm1.Enabled = False
    

    'Set objWorkDoc = WordServer.Documents.Add Template := "d:\fineTable.dot"
        
    With objWorkDoc
        
        'MsgBox objWorkDoc.Tables.count

        '.Content.InsertAfter "Слой: " & UserForm1.LayerSelectComboBox.Text & vbCrLf
        'If UserForm1.CB_CalcLayerArea.Value Then _
        '    .Content.InsertAfter "Площадь: " & _
        '        Format(SumArea, "0.0000") & vbCrLf & vbCrLf Else .Content.InsertAfter vbCrLf
                
        UserForm1.ProgressBar1.Visible = True
        UserForm1.ProgressBar1.Max = UBound(ssobjs) + 1
        
        k = 0               ' Номер текущей вершины
        YP = 1              ' Вертикальная позиция курсора вставки
        XP = 1              ' Горизонтальная позиция курсора вставки
        nPage = 1           ' Номер страницы
        nColNum = 0         ' Номер столбца
        nLastYP = YP        ' Позиция начала страницы по вертикали
                
        'MsgBox UBound(ssobjs)
        
        For i = 0 To UBound(ssobjs)
            Set PolyLine = ssobjs(RefArr(i).SSIndex)
            
            ' Расставляем номера полигонов в гиперссылки
            If UserForm1.CB_InsNumbers.Value Then
                Set Hyperlinks = PolyLine.Hyperlinks
                If Hyperlinks.count >= 1 Then ' Удаляем все гиперлинки
                    For Each Hyperlink In Hyperlinks
                        Hyperlink.Delete
                    Next Hyperlink
                End If
                Set Hyperlink = Hyperlinks.Add("")
                Hyperlink.URLDescription = i + 1
            End If
            
            ' Вставляем номер полигона
            objWorkDoc.Tables(1).cell(YP, XP + nColNum).Range.InsertAfter (i + 1)
                                    
            For j = 0 To UBound(PolyLine.Coordinates) Step 2
                
                k = k + 1   ' Номер вершины
                
                ' Извлекаем и преобразовываем координыты текущей вершины
                OnePoint(0) = PolyLine.Coordinates(j)
                OnePoint(1) = PolyLine.Coordinates(j + 1)
                OnePoint(2) = PolyLine.Elevation
                pointUCS = ThisDrawing.Utility.TranslateCoordinates(OnePoint, acWorld, acUCS, False, PolyLine.Normal)
                XRep = Format(pointUCS(0), "0.0000")
                YRep = Format(pointUCS(1), "0.0000")
                                
                ' Вводим в таблицу: номер вершины; координату по X; координату по Y
                objWorkDoc.Tables(1).cell(YP, XP + nColNum + 1).Range.InsertAfter (k)
                objWorkDoc.Tables(1).cell(YP, XP + nColNum + 2).Range.InsertAfter (XRep)
                objWorkDoc.Tables(1).cell(YP, XP + nColNum + 3).Range.InsertAfter (YRep)
                
                ' Если текущая строка не является последней на странице
                If ((nPage = 1) And (YP < 25)) Or ((nPage > 1) And (YP - nLastYP < 29)) Then
                    YP = YP + 1 ' Переходим на следующую строку
                Else 'Иначе - текущая строка последняя
                
                    ' Если это последня координата полигона и текущая строка последняя
                    'If j + 1 >= UBound(PolyLine.Coordinates) Then
                    '   With objWorkDoc.Tables(1).cell(YP, XP + nColNum).Borders(-3)
                    '    .LineStyle = 1
                    '    .LineWidth = 18
                    '   End With
                    'End If
                    
                    If nColNum > 4 Then 'Если последняя строка в последнем столбце - переходим к новой странице
                       nColNum = 0
                       YP = YP + 1
                       nLastYP = YP
                       nPage = nPage + 1
                       
                       ' Добавляем 30 новых строк в таблицу
                       For tt = 1 To 30
                           objWorkDoc.Tables(1).Rows.Add
                           'DoEvents
                       Next
                       
                    Else 'Иначе - последняя строка, но не последний столбец
                       nColNum = nColNum + 4
                       YP = nLastYP
                    End If
                    
                    If j + 1 < UBound(PolyLine.Coordinates) Then
                       objWorkDoc.Tables(1).cell(YP, XP + nColNum).Range.InsertAfter (i + 1)
                    End If
                    
                End If
                DoEvents
                
            Next
            
            ' Проводим линию в таблице под последней координатой в полигоне
            With objWorkDoc.Tables(1).cell(YP - 1, XP + nColNum).Borders(-3)
                .LineStyle = 1
                .LineWidth = 8
            End With
            
            ' Если опция "Сквозная нумерация" не выбрана, то обнуляем счетчик номера вершины
            If Not UserForm1.CBDirectCounting.Value Then k = 0
            
            ' Обновим показания прогресс-бара
            UserForm1.ProgressBar1.Value = i + 1
            DoEvents
        Next
       
    End With
    
ОбработкаОшибок:
    
    WordServer.ScreenRefresh
    WordServer.ScreenUpdating = True
    
    WordServer.Visible = True
    UserForm1.ProgressBar1.Visible = False
    UserForm1.Enabled = True

End Function

Private Sub GetVal(ByVal RavVal As AcadEntity, ByRef Rec As RefRecType)
    Dim minExt As Variant
    Dim maxExt As Variant
    Dim pointUCS  As Variant
    
    RavVal.GetBoundingBox minExt, maxExt
    
    pointUCS = ThisDrawing.Utility.TranslateCoordinates(minExt, acWorld, acUCS, False, RavVal.Normal)
    Rec.SKeyX = pointUCS(0)
    Rec.SKeyY = pointUCS(1)
    
    pointUCS = ThisDrawing.Utility.TranslateCoordinates(maxExt, acWorld, acUCS, False, RavVal.Normal)
    Rec.SKey1X = pointUCS(0)
    Rec.SKey1Y = pointUCS(1)
    Rec.SKey1 = pointUCS(0) + pointUCS(1)
        
End Sub

Static Sub QuickSortPolylines(ByRef Arr() As RefRecType, ByVal L As Integer, ByVal R As Integer)
    Dim i, n As Integer
               
    ' Сортируем по минимальной точке
    QuickSortPolylinesHV Arr, L, R
    
    ' Теперь сортитуем по максимальной
    n = L
    
    For i = L To R - 1
        If (Arr(i).SKeyY <> Arr(i + 1).SKeyY) Or (Arr(i).SKeyX <> Arr(i + 1).SKeyX) Then
            If i - n >= 1 Then QuickSortPolylines1HV Arr, n, i
            n = i + 1
        End If
    Next
    
    If (Arr(R - 1).SKeyY = Arr(R).SKeyY) And (Arr(R - 1).SKeyX = Arr(R).SKeyX) And (R - n >= 1) Then
        QuickSortPolylines1HV Arr, n, R
    End If
    
End Sub

Static Sub QuickSortPolylinesHV(ByRef Arr() As RefRecType, ByVal L As Integer, ByVal R As Integer)
    Dim i, n As Integer
            
    ' Сортируем по горизонтали
    QuickSortPolylinesH Arr, L, R
    
    ' Теперь по вертикали
    n = L
    
    For i = L To R - 1
        If Arr(i).SKeyX <> Arr(i + 1).SKeyX Then
            If i - n >= 1 Then QuickSortPolylinesV Arr, n, i
            n = i + 1
        End If
    Next
    
    If (Arr(R - 1).SKeyX = Arr(R).SKeyX) And (R - n >= 1) Then QuickSortPolylinesV Arr, n, R
    
End Sub

Static Sub QuickSortPolylinesH(ByRef Arr() As RefRecType, ByVal L As Integer, ByVal R As Integer)
    Dim i, j As Integer
    Dim pX As Double
    
    Do
        i = L
        j = R
        pX = Arr((L + R) \ 2).SKeyX
        
        Do
            Do While (Arr(i).SKeyX < pX)
                i = i + 1
            Loop
            Do While (Arr(j).SKeyX > pX)
                j = j - 1
            Loop
            If i <= j Then
                If (Arr(i).SKeyX <> Arr(j).SKeyX) Then SwapElements Arr, i, j
                i = i + 1
                j = j - 1
            End If
        Loop Until i > j
        
        If L < j Then QuickSortPolylinesH Arr, L, j
        L = i
    Loop Until i >= R

End Sub

Static Sub QuickSortPolylinesV(ByRef Arr() As RefRecType, ByVal L As Integer, ByVal R As Integer)
    Dim i, j As Integer
    Dim pY As Double

    Do
        i = L
        j = R
        pY = Arr((L + R) \ 2).SKeyY
        
        Do
            Do While (Arr(i).SKeyY < pY)
                i = i + 1
            Loop
            Do While (Arr(j).SKeyY > pY)
                j = j - 1
            Loop
            If i <= j Then
                If (Arr(i).SKeyY <> Arr(j).SKeyY) Then SwapElements Arr, i, j
                i = i + 1
                j = j - 1
            End If
        Loop Until i > j
        
        If L < j Then QuickSortPolylinesV Arr, L, j
        L = i
    Loop Until i >= R

End Sub

Static Sub QuickSortPolylines1HV(ByRef Arr() As RefRecType, ByVal L As Integer, ByVal R As Integer)
    Dim i, j As Integer
    Dim pY As Double

    'MsgBox "L, R = " & L & " ;  " & R
    
    Do
        i = L
        j = R
        pY = Arr((L + R) \ 2).SKey1
        
        Do
            Do While (Arr(i).SKey1 < pY)
                i = i + 1
            Loop
            Do While (Arr(j).SKey1 > pY)
                j = j - 1
            Loop
            If i <= j Then
                If (Arr(i).SKey1 <> Arr(j).SKey1) Then SwapElements Arr, i, j
                i = i + 1
                j = j - 1
            End If
        Loop Until i > j
        
        If L < j Then QuickSortPolylines1HV Arr, L, j
        L = i
    Loop Until i >= R

End Sub

Sub SwapElements(ByRef Arr() As RefRecType, ByVal n As Integer, ByVal n1 As Integer)
    Dim Buf As RefRecType
            
    Buf = Arr(n)
    Arr(n) = Arr(n1)
    Arr(n1) = Buf
    
End Sub

Public Sub ConnectWord(x As Variant)
    ' X is only used to suppress this routine from the Run Macro Dialog

    ' Determine the versions Word that we have available on this machine,
    ' and set the public variables accordingly
    
    On Error Resume Next
       
    WordVer = 0
    
    '---------------------------------
    ' Try to find a version of Word 8
    '---------------------------------
    
    ' Attempt to activate an existing instance
    Err.Clear
    Set WordServer = GetObject(, "Word.Application.8")
    If Err.Number = 0 Then
        WordVer = 8
        GoTo FINISH
    End If
    
    ' Create a new instance
    Err.Clear
    Set WordServer = CreateObject("Word.Application.8")
    If Err.Number = 0 Then
        WordVer = 8
        GoTo FINISH
    End If
    
    '---------------------------------
    ' Try to find a version of Word 7
    '---------------------------------
    
    ' Attempt to activate an existing instance
    Err.Clear
    Set WordServer = GetObject(, "Word.Application.7")
    If Err.Number = 0 Then
        WordVer = 7
        GoTo FINISH
    End If
    
    ' Create a new instance
    Err.Clear
    Set WordServer = CreateObject("Word.Application.7")
    If Err.Number = 0 Then
        WordVer = 7
        GoTo FINISH
    End If
    
FINISH:
    ' If we don't have Word installed, refuse to run
    If (WordVer = 0) Then
        MsgBox "Для экспорта данных на вашей машине должен быть установлен в MS Word 97 или лучше", vbCritical, appName
        Exit Sub
    End If

    WordServer.WindowState = -4140 ' xlMinimized
    'WordServer.Visible = False  ' Make it visible
    
End Sub

Function GetProjectFilePath() As String

    ' This example finds the current project file information.
    
    Dim preferences As AcadPreferences
    Set preferences = ThisDrawing.Application.preferences
    
    ' Get the current project file information
    Dim currProjPath As String
    Dim currProjName As Variant
    currProjName = ThisDrawing.GetVariable("PROJECTNAME")

    If currProjName <> "" Then
        currProjPath = preferences.Files.GetProjectFilePath(currProjName)
    End If
    If currProjPath = "" Then
        MsgBox "There is no current project file or path. ", , "GetProjectFilePath Example"
    Else
        MsgBox "The current project file path is: " & currProjPath, , "GetProjectFilePath Example"
    End If
        
    GetProjectFilePath = currProjPath

End Function

Attribute VB_Name = "ShowAreaForm"
Attribute VB_Base = "0{A0513BA6-0E14-11D4-ACA6-444553540000}{A0513B8A-0E14-11D4-ACA6-444553540000}"
Attribute VB_Creatable = False
Attribute VB_PredeclaredId = True
Attribute VB_Exposed = False
Attribute VB_TemplateDerived = False
Attribute VB_Customizable = False
Private Sub CommandButton1_Click()
    hide
End Sub

Private Sub Image1_Click()

End Sub

Private Sub UserForm_Click()

End Sub

Attribute VB_Name = "UserForm1"
Attribute VB_Base = "0{A0513C0E-0E14-11D4-ACA6-444553540000}{A0513B82-0E14-11D4-ACA6-444553540000}"
Attribute VB_Creatable = False
Attribute VB_PredeclaredId = True
Attribute VB_Exposed = False
Attribute VB_TemplateDerived = False
Attribute VB_Customizable = False

'       Экспорт данных текущего слоя в Microsoft Word
'       Copyright (C) 1999 by Александр Беляев
'
'       Главная форма управления программой



Private Sub CommandButton1_Click()
    End
End Sub

Private Sub CommandButton2_Click()
    ExportData False
End Sub

Function CheckLayer() As Boolean
    'ThisDrawing.ActiveLayer
    'ThisDrawing.ModelSpace.
End Function

Private Sub StatusBar1_PanelClick(ByVal Panel As ComctlLib.Panel)

End Sub

Private Sub Image2_Click()

End Sub

Private Sub CommandButton3_Click()
    ExportData True
End Sub

Private Sub Label1_Click()

End Sub

Private Sub CommandButton5_Click()
    End
End Sub

Private Sub ProgressBar1_MouseDown(ByVal Button As Integer, ByVal Shift As Integer, ByVal x As stdole.OLE_XPOS_PIXELS, ByVal y As stdole.OLE_YPOS_PIXELS)

End Sub

Private Sub UserForm_Click()

End Sub
